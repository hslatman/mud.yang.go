module ietf-acl-tls {
  yang-version 1.1;
  namespace "urn:ietf:params:xml:ns:yang:ietf-acl-tls";
  prefix ietf-acl-tls;

  import iana-tls-profile {
    prefix ianatp;
    reference
      "RFC XXXX: Manufacturer Usage Description (MUD) (D)TLS
                 Profiles for IoT Devices";
  }
  import ietf-crypto-types {
    prefix ct;
    reference
      "RFC CCCC: Common YANG Data Types for Cryptography";
  }
  import iana-hash-algs {
    prefix iha;
    reference
      "RFC IIII: Common YANG Data Types for
       Hash algorithms";
  }
  import ietf-access-control-list {
    prefix acl;
    reference
      "RFC 8519: YANG Data Model for Network Access
                 Control Lists (ACLs)";
  }

  organization
    "IETF OPSAWG (Operations and Management Area Working Group)";
  contact
    "WG Web: <https://datatracker.ietf.org/wg/opsawg/>
     WG List: opsawg@ietf.org

      Author: Konda, Tirumaleswar Reddy
                   TirumaleswarReddy_Konda@McAfee.com
    ";
  description
    "This YANG module defines a component that augments the
      IETF description of an access list to allow (D)TLS profile
      as matching criteria.

     Copyright (c) 2020 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC XXXX; see
     the RFC itself for full legal notices.";
  revision 2020-11-02 {
    description
      "Initial revision";
    reference
      "RFC XXXX: Manufacturer Usage Description (MUD) (D)TLS
                 Profiles for IoT Devices";
  }

  feature tls-1-2 {
    description
      "TLS Protocol Version 1.2 is supported.";
    reference
      "RFC 5246: The Transport Layer Security (TLS) Protocol
                 Version 1.2";
  }

  feature tls-1-3 {
    description
      "TLS Protocol Version 1.3 is supported.";
    reference
      "RFC 8446: The Transport Layer Security (TLS) Protocol
                 Version 1.3";
  }

  feature dtls-1-2 {
    description
      "DTLS Protocol Version 1.2 is supported.";
    reference
      "RFC 6346: Datagram Transport Layer Security
                 Version 1.2";
  }

  feature dtls-1-3 {
    description
      "DTLS Protocol Version 1.3 is supported.";
    reference
      "draft-ietf-tls-dtls13: Datagram Transport Layer
                Security 1.3";
  }

  feature match-on-tls-dtls {
    description
      "The networking device can support matching on
       (D)TLS parameters.";
  }

  augment "/acl:acls/acl:acl/acl:aces/acl:ace/acl:matches" {
    if-feature "match-on-tls-dtls";
    description
      "(D)TLS specific matches.";
    container client-profile {
      description
        "A grouping for (D)TLS profiles.";
      container client-profile {
        description
          "A grouping for DTLS profiles.";
        list tls-dtls-profiles {
          key "profile-name";
          description
            "A list of (D)TLS version profiles supported by
             the client.";
          leaf profile-name {
            type string {
              length "1..64";
            }
            description
              "The name of (D)TLS profile; space and special
               characters are not allowed.";
          }
          leaf-list supported-tls-versions {
            type ianatp:tls-version;
            description
              "TLS versions supported by the client.";
          }
          leaf-list supported-dtls-versions {
            type ianatp:dtls-version;
            description
              "DTLS versions supported by the client.";
          }
          list cipher-suites {
            key "cipher hash";
            leaf cipher {
              type ianatp:cipher-algorithm;
              description
                "AEAD encryption algorithm as defined in RFC5116.";
            }
            leaf hash {
              type ianatp:hash-algorithm;
              description
                "Hash algorithm used with HKDF as defined in RFC5869.";
            }
            description
              "A list of Cipher Suites supported by the client.";
          }
          leaf-list extension-types {
            type ianatp:extension-type;
            description
              "A list of Extension Types supported by the client.";
          }
          leaf-list acceptlist-ta-certs {
            type ct:trust-anchor-cert-cms;
            description
              "A list of trust anchor certificates used by the client.";
          }
          container spki {
            description
              "A grouping for spki.";
            leaf-list spki-pin-sets {
              type ianatp:spki-pin-set;
              description
                "A list of SPKI pin sets pre-configured on the client
                 to validate self-signed server certificate or
                 raw public key.";
            }
            leaf spki-hash-algorithm {
              type iha:hash-algorithm-type;
              description
                "cryptographic hash algorithm used to generate the
                 SPKI pinset.";
            }
          }
          leaf-list psk-key-exchange-modes {
            if-feature "tls-1-3 or dtls-1-3";
            type ianatp:psk-key-exchange-mode;
            description
              "pre-shared key exchange modes.";
          }
          leaf-list supported-groups {
            type ianatp:supported-group;
            description
              "A list of named groups supported by the client.";
          }
          leaf-list signature-algorithms-cert {
            if-feature "tls-1-3 or dtls-1-3";
            type ianatp:signature-algorithm;
            description
              "A list signature algorithms the client can validate
               in X.509 certificates.";
          }
          leaf-list signature-algorithms {
            type ianatp:signature-algorithm;
            description
              "A list signature algorithms the client can validate
               in the CertificateVerify message.";
          }
          leaf-list application-protocols {
            type ianatp:application-protocol;
            description
              "A list application protocols supported by the client.";
          }
          leaf-list cert-compression-algorithms {
            if-feature "tls-1-3 or dtls-1-3";
            type ianatp:cert-compression-algorithm;
            description
              "A list certificate compression algorithms
               supported by the client.";
          }
          leaf-list certificate-authorities {
            if-feature "tls-1-3 or dtls-1-3";
            type ianatp:certificate-authority;
            description
              "A list of the distinguished names of certificate authorities
               acceptable to the client.";
          }
        }
      }
    }
  }
}

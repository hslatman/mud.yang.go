module ietf-mud-transparency {
  yang-version 1.1;
  namespace "urn:ietf:params:xml:ns:yang:ietf-mud-transparency";
  prefix mud-transparency;

  import ietf-inet-types {
    prefix inet;
    reference "RFC 6991";
}
  import ietf-mud {
    prefix mud;
    reference "RFC 8520";
  }

  organization
    "IETF OPSAWG (Ops Area) Working Group";
  contact
    "WG Web: http://tools.ietf.org/wg/opsawg/
     WG List: opsawg@ietf.org

     Editor: Eliot Lear lear@cisco.com
     Editor: Scott Rose scott.rose@nist.gov";
  description
    "This YANG module augments the ietf-mud model to provide for
     reporting of SBOMs.

     Copyright (c) 2020 IETF Trust and the persons identified as
     authors of the code.  All rights reserved.

     Redistribution and use in source and binary forms, with or
     without modification, is permitted pursuant to, and subject to
     the license terms contained in, the Simplified BSD License set
     forth in Section 4.c of the IETF Trust's Legal Provisions
     Relating to IETF Documents
     (https://trustee.ietf.org/license-info).

     This version of this YANG module is part of RFC XXXX
     (https://www.rfc-editor.org/info/rfcXXXX); 
     see the RFC itself for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.  ";

  revision 2021-07-06 {
    description
      "Initial proposed standard.";
    reference
      "RFC XXXX: Extension for software transparency";
  }

  grouping transparency-extension {
    description
      "Transparency extension grouping";
    container transparency {
      description
        "container of methods to get an SBOM.";
      choice sbom-retrieval-method {
        description
          "How to find SBOM information";
        case cloud {
          list sboms {
            key "version-info";
            description
              "A list of SBOMs tied to different s/w
               or h/w versions.";
            leaf version-info {
              type string;
              description
                "The version to which this SBOM refers.";
            }
            leaf sbom-url {
              type inet:uri;
              description
                "A statically located URI.";
            }
          }
        }
        case local-well-known {
          leaf sbom-local-well-known {
            type enumeration {
              enum http {
                description
                  "Use http (insecure) to retrieve 
                   SBOM information.";
              }
              enum https {
                description
                  "Use https (secure) to retrieve SBOM information.";
              }
              enum coap {
                description
                  "Use COAP (insecure) to retrieve SBOM";
              }
              enum coaps {
                description
                  "Use COAPS (secure) to retrieve SBOM";
              }
              enum openc2 {
                description
                  "Use OpenC2 endpoint.
                   This is https://{host}/.well-known/openc2";
              }
            }
            description
              "Which communication protocol to choose.";
          }
        }
        case sbom-contact-info {
          leaf sbom-contact-uri {
            type inet:uri;
            mandatory true;
            description
              "This MUST be either a tel, http, https, or
               mailto uri schema that customers can use to
               contact someone for SBOM information.";
          }
        }
      }
      choice vuln-retrieval-method {
        description
          "How to find vulnerability information";
        case cloud {
          leaf vuln-url {
            type inet:uri;
            description
              "A statically located URL.";
          }
        }
        case vuln-contact-info {
          leaf contact-uri {
            type inet:uri;
            mandatory true;
            description
              "This MUST be either a tel, http, https, or
               mailto uri schema that customers can use to
               contact someone for vulnerability information.";
          }
        }
      }
    }
  }

  augment "/mud:mud" {
    description
      "Add extension for software transparency.";
    uses transparency-extension;
  }
}
